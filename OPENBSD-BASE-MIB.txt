--
-- $jwk$
--
--
-- Copyright (c) 2004-2007 Joel Knight <knight.joel@gmail.com>
--
-- Permission to use, copy, modify, and distribute this document for any
-- purpose with or without fee is hereby granted, provided that the above
-- copyright notice and this permission notice appear in all copies.
--
-- THE DOCUMENT IS PROVIDED "AS IS" AND THE AUTHOR DISCLAIMS ALL WARRANTIES
-- WITH REGARD TO THIS DOCUMENT INCLUDING ALL IMPLIED WARRANTIES OF
-- MERCHANTABILITY AND FITNESS. IN NO EVENT SHALL THE AUTHOR BE LIABLE FOR
-- ANY SPECIAL, DIRECT, INDIRECT, OR CONSEQUENTIAL DAMAGES OR ANY DAMAGES
-- WHATSOEVER RESULTING FROM LOSS OF USE, DATA OR PROFITS, WHETHER IN AN
-- ACTION OF CONTRACT, NEGLIGENCE OR OTHER TORTIOUS ACTION, ARISING OUT OF
-- OR IN CONNECTION WITH THE USE OR PERFORMANCE OF THIS DOCUMENT.


OPENBSD-BASE-MIB DEFINITIONS ::= BEGIN

IMPORTS
	MODULE-IDENTITY, NOTIFICATION-TYPE, OBJECT-TYPE, enterprises
		FROM SNMPv2-SMI

	MODULE-COMPLIANCE, OBJECT-GROUP
		FROM SNMPv2-CONF;

openBSD MODULE-IDENTITY
    LAST-UPDATED "200612100000Z"
    ORGANIZATION "OpenBSD"
    CONTACT-INFO "
                  Author:     Joel Knight
                  email:      knight.joel@gmail.com
                  www:        www.packetmischief.ca/openbsd-snmp-mibs/
                 "
    DESCRIPTION "The base MIB module for the OpenBSD project."
-- FIXME: http://www.iana.org/assignments/smi-numbers
    ::= { enterprises 64512 }


-- define MIB objects

-- OPENBSD-PF-MIB:
pfMIBObjects				OBJECT IDENTIFIER ::= { openBSD 1 }
sensorsMIBObjects			OBJECT IDENTIFIER ::= { openBSD 2 }
carpMIBObjects				OBJECT IDENTIFIER ::= { openBSD 3 }


-- END:  Don't forget this!
END
